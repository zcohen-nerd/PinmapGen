#usage "PinmapGen ULP with Automatic Netlist Generation"

// ── Path discovery ─────────────────────────────────────────────────────────
// All paths are derived from where this ULP lives or loaded from a settings
// file saved next to it. Nothing is hardcoded to a specific machine.

string ulpDir = filedir(argv[0]);
string settingsFile = ulpDir + "PinmapGen_settings.txt";

// Default settings (overridden by the settings file when present)
string mcuRef = "U1";
string outputDir = ulpDir + "PinmapGen_Output";
string projectName = "Project";
string mcuType = "rp2040";
string repoDir = "";   // Path to the cloned PinmapGen repository (required)
int settingsLoaded = 0;  // set by loadSettings when a settings file was read
int generateMicroPython = 1;
int generateArduino = 1;
int generateMarkdown = 1;
int generateMermaid = 1;

// MCU profiles bundled with PinmapGen (see tools/pinmapgen/profiles/)
string validMcuList = "rp2040 rp2350 esp32 esp32s3 esp32c3 stm32g0 stm32f411 stm32h743 nrf52840 atmega328p atmega2560 atsamd21 atsamd51";

int isValidMcu(string candidate) {
    string parts[];
    int n = strsplit(parts, validMcuList, ' ');
    for (int i = 0; i < n; i++) {
        if (parts[i] == candidate) return 1;
    }
    return 0;
}

string trimCr(string s) {
    int len = strlen(s);
    if (len > 0 && s[len - 1] == '\r') {
        return strsub(s, 0, len - 1);
    }
    return s;
}

// Escape a value for embedding inside a PowerShell single-quoted string
// (single quotes are doubled). Prevents apostrophes in project names or
// paths from breaking the generated command.
string psEscape(string s) {
    string result = "";
    for (int i = 0; i < strlen(s); i++) {
        if (s[i] == '\'') result += "''";
        else result += strsub(s, i, 1);
    }
    return result;
}

// Convert an EAGLE-style forward-slash path to backslashes for cmd.exe,
// which rejects forward-slash separators.
string toWindowsPath(string path) {
    string parts[];
    strsplit(parts, path, '/');
    return strjoin(parts, '\\');
}

// Clean a user-entered path or field: trim whitespace, strip the
// wrapping quotes Explorer's "Copy as path" adds, and normalize
// backslashes to the forward slashes EAGLE uses internally.
string cleanPath(string p) {
    int start = 0;
    int end = strlen(p);
    while (start < end && (p[start] == ' ' || p[start] == '\t' || p[start] == '"')) start++;
    while (end > start && (p[end - 1] == ' ' || p[end - 1] == '\t' || p[end - 1] == '"' || p[end - 1] == '\r')) end--;
    string trimmed = strsub(p, start, end - start);
    string parts[];
    strsplit(parts, trimmed, '\\');
    return strjoin(parts, '/');
}

// Default output location: the user's Documents folder when this ULP
// lives in the usual AppData ULP directory - AppData is hidden, often
// write-protected, and wiped on a Fusion reinstall.
string defaultOutputDir() {
    int at = strstr(ulpDir, "/AppData/");
    if (at > 0) {
        return strsub(ulpDir, 0, at) + "/Documents/PinmapGen_Output";
    }
    return ulpDir + "PinmapGen_Output";
}

// Escape a CSV field value: double any embedded quotes so a quote in a
// net name cannot corrupt the row.
string csvField(string s) {
    string result = "";
    for (int i = 0; i < strlen(s); i++) {
        if (s[i] == '"') result += "\"\"";
        else result += strsub(s, i, 1);
    }
    return result;
}

// Read the CLI's --log-file back in; returns "" when the file is missing
// (which means Python never started).
string readLogFile(string path) {
    string found[];
    if (fileglob(found, path) == 0) return "";
    string content = "";
    if (fileread(content, path) <= 0) return "";
    return content;
}

// The CLI prefixes every problem line with one of these markers; any hit
// means the run deserves review even though files were written.
int logHasIssues(string logText) {
    if (strstr(logText, "Warning:") >= 0) return 1;
    if (strstr(logText, "Validation error:") >= 0) return 1;
    if (strstr(logText, "Error:") >= 0) return 1;
    return 0;
}

// Show a run's outcome with the full CLI log in a scrollable view -
// dlgMessageBox cannot scroll long output.
void showRunLog(string title, string message, string logText) {
    int r = dlgDialog(title) {
        dlgVBoxLayout {
            dlgLabel(message);
            dlgSpacing(5);
            dlgTextView(logText);
            dlgSpacing(5);
            dlgHBoxLayout {
                dlgStretch(1);
                dlgPushButton("+OK") dlgAccept();
            }
        }
    };
}

// Probe one interpreter candidate: run "<candidate> --version" via
// cmd.exe, capture the output, and require exit code 0 plus a version
// of 3.11 or newer. The Microsoft Store's fake python.exe alias fails
// this probe (it exits non-zero), so it can't be picked by mistake.
int probePython(string candidate, string probeFile) {
    string winProbe = toWindowsPath(probeFile);
    int rc = system("cmd.exe /c " + candidate + " --version > \"" + winProbe + "\" 2>&1");
    if (rc != 0) return 0;
    string out = "";
    if (fileread(out, probeFile) <= 0) return 0;
    int at = strstr(out, "Python ");
    if (at < 0) return 0;
    string parts[];
    int n = strsplit(parts, strsub(out, at + 7), '.');
    if (n < 2) return 0;
    int major = strtol(parts[0]);
    int minor = strtol(parts[1]);
    if (major > 3) return 1;
    if (major == 3 && minor >= 11) return 1;
    return 0;
}

// Find a Python 3.11+ interpreter: try "python" on PATH first, then the
// "py -3" launcher, which the python.org installer provides even when
// the "Add python.exe to PATH" box was left unticked - the single most
// common install mistake. Returns the command to use, or "" when no
// suitable interpreter exists.
string findPython(string probeDir) {
    string probeFile = probeDir + "/python_probe.txt";
    string found = "";
    if (probePython("python", probeFile)) found = "python";
    else if (probePython("py -3", probeFile)) found = "py -3";
    system("cmd.exe /c del \"" + toWindowsPath(probeFile) + "\" 2>nul");
    return found;
}

// Reference designators are passed to the CLI unquoted, so restrict them
// to safe characters (letters, digits, underscore, hyphen).
int isSafeRefDes(string s) {
    if (strlen(s) == 0) return 0;
    for (int i = 0; i < strlen(s); i++) {
        char c = s[i];
        int ok = (c >= 'A' && c <= 'Z') || (c >= 'a' && c <= 'z') ||
                 (c >= '0' && c <= '9') || c == '_' || c == '-';
        if (!ok) return 0;
    }
    return 1;
}

// Function to generate timestamped project name. A previous "_<epoch>"
// suffix is stripped first so repeated clicks replace the timestamp
// instead of compounding it forever.
string generateProjectName(string baseName) {
    int us = strrchr(baseName, '_');
    if (us > 0) {
        string tail = strsub(baseName, us + 1);
        int digits = strlen(tail) >= 9;
        for (int i = 0; digits && i < strlen(tail); i++) {
            if (tail[i] < '0' || tail[i] > '9') digits = 0;
        }
        if (digits) baseName = strsub(baseName, 0, us);
    }
    string timestamp;
    sprintf(timestamp, "%u", time());
    return baseName + "_" + timestamp;
}

// Windows filenames may not contain these characters.
int isSafeProjectName(string s) {
    if (strlen(s) == 0) return 0;
    for (int i = 0; i < strlen(s); i++) {
        char c = s[i];
        if (c == '\\' || c == '/' || c == ':' || c == '*' || c == '?' ||
            c == '"' || c == '<' || c == '>' || c == '|') return 0;
    }
    return 1;
}

// True when a part with this reference designator exists in the open
// schematic (case-insensitive).
int refdesExists(string ref) {
    string want = ref;
    want = strupr(want);
    int found = 0;
    if (schematic) {
        schematic(S) {
            S.parts(P) {
                string pn = P.name;
                pn = strupr(pn);
                if (pn == want) found = 1;
            }
        }
    }
    return found;
}

// Load settings from the file saved next to this ULP (if it exists)
void loadSettings() {
    string found[];
    if (fileglob(found, settingsFile) == 0) return;

    string content;
    if (fileread(content, settingsFile) <= 0) return;
    settingsLoaded = 1;

    string lines[];
    int n = strsplit(lines, content, '\n');
    for (int i = 0; i < n; i++) {
        string line = trimCr(lines[i]);
        int eq = strchr(line, '=');
        if (eq <= 0) continue;
        string key = strsub(line, 0, eq);
        string val = strsub(line, eq + 1);
        if (key == "mcuRef") mcuRef = cleanPath(val);
        else if (key == "outputDir") outputDir = cleanPath(val);
        else if (key == "projectName") projectName = val;
        else if (key == "mcuType") mcuType = cleanPath(val);
        else if (key == "repoDir") repoDir = cleanPath(val);
        else if (key == "generateMicroPython") generateMicroPython = (val == "1");
        else if (key == "generateArduino") generateArduino = (val == "1");
        else if (key == "generateMarkdown") generateMarkdown = (val == "1");
        else if (key == "generateMermaid") generateMermaid = (val == "1");
    }
}

// Save settings next to this ULP for the next run
void saveSettings() {
    output(settingsFile) {
        printf("# PinmapGen ULP settings - saved automatically\n");
        printf("mcuRef=%s\n", mcuRef);
        printf("outputDir=%s\n", outputDir);
        printf("projectName=%s\n", projectName);
        printf("mcuType=%s\n", mcuType);
        printf("repoDir=%s\n", repoDir);
        printf("generateMicroPython=%d\n", generateMicroPython);
        printf("generateArduino=%d\n", generateArduino);
        printf("generateMarkdown=%d\n", generateMarkdown);
        printf("generateMermaid=%d\n", generateMermaid);
    }
}

// Function to analyze schematic and detect issues
string analyzeSchematic(string targetMcuRef) {
    string warnings;
    warnings = "";
    int mcuFound = 0;
    int componentCount = 0;
    int netCount = 0;
    int pinCount = 0;

    if (!schematic) {
        return "No schematic open";
    }

    schematic(S) {
        S.sheets(SH) {
            SH.nets(N) {
                netCount++;
                N.segments(SEG) {
                    SEG.pinrefs(PR) {
                        if (PR.part && PR.pin) {
                            componentCount++;

                            // Check if this is the target MCU
                            if (PR.part.name == targetMcuRef) {
                                mcuFound = 1;

                                string pinNum = PR.pin.name;
                                PR.pin.contacts(C) {
                                    pinNum = C.name;
                                    break;
                                }

                                // Count pins (simplified conflict detection)
                                pinCount++;
                            }
                        }
                    }
                }
            }
        }
    }

    // Generate summary and warnings
    string summary;
    string pinCountStr;
    string componentCountStr;
    string netCountStr;

    sprintf(pinCountStr, "%d", pinCount);
    sprintf(componentCountStr, "%d", componentCount);
    sprintf(netCountStr, "%d", netCount);

    if (!mcuFound) {
        summary = "MCU reference '" + targetMcuRef + "' not found in schematic\n";
    } else {
        summary = "Found MCU " + targetMcuRef + " with " + pinCountStr + " pins\n";
    }

    summary = summary + "Schematic has " + componentCountStr + " connections across " + netCountStr + " nets\n";

    if (strlen(warnings) > 0) {
        return summary + "\nWARNINGS:\n" + warnings;
    } else {
        return summary + "\nAnalysis complete";
    }
}

// Function to validate input parameters
string validateInputs(string mcuRefIn, string outputDirIn, string projectNameIn, string repoDirIn) {
    string errors = "";

    if (!isSafeRefDes(mcuRefIn)) {
        errors += "- MCU Reference must be non-empty and contain only letters, digits, '_' or '-'\n";
    }

    if (strlen(outputDirIn) == 0) {
        errors += "- Base Output Directory cannot be empty\n";
    }

    if (!isSafeProjectName(projectNameIn)) {
        errors += "- Project Name must be non-empty and free of \\ / : * ? \" < > |\n";
    }

    if (strchr(outputDirIn, '"') >= 0 || strchr(repoDirIn, '"') >= 0) {
        errors += "- Paths must not contain quote characters\n";
    }

    if (strlen(repoDirIn) == 0) {
        errors += "- PinmapGen repository path cannot be empty.\n" +
                  "  Clone https://github.com/zcohen-nerd/PinmapGen and enter the folder path.\n";
    } else {
        string cliCheck[];
        if (fileglob(cliCheck, repoDirIn + "/tools/pinmapgen/cli.py") == 0) {
            errors += "- '" + repoDirIn + "' does not look like the PinmapGen repository\n" +
                      "  (tools/pinmapgen/cli.py not found there)\n";
        }
    }

    return errors;
}

// Function to generate netlist CSV directly from schematic
int generateNetlistCSV(string netlistPath) {
    if (!schematic) {
        return -1; // No schematic available
    }

    int componentCount = 0;
    int netCount = 0;
    int success = 0;

    // First pass: count components and nets for validation
    schematic(S) {
        S.sheets(SH) {
            SH.nets(N) {
                netCount++;
                N.segments(SEG) {
                    SEG.pinrefs(PR) {
                        if (PR.part && PR.pin) {
                            componentCount++;
                        }
                    }
                }
            }
        }
    }

    if (componentCount == 0) {
        return -2; // No components found
    }

    if (netCount == 0) {
        return -3; // No nets found
    }

    // Second pass: generate CSV
    output(netlistPath) {
        printf("\"RefDes\",\"Pin\",\"Component\",\"Net\",\"Pad\"\n");

        schematic(S) {
            S.sheets(SH) {
                SH.nets(N) {
                    N.segments(SEG) {
                        SEG.pinrefs(PR) {
                            if (PR.part && PR.pin) {
                                // Use the SYMBOL pin name (GP4, PA0,
                                // GPIO15...) for the Pin column, never the
                                // package pad number: pad 2 of an RP2040
                                // is GPIO0, and the CLI reads a bare "2"
                                // as GP2 - a plausible but wrong pinmap.
                                // The physical pad is still exported in
                                // the extra Pad column for debugging;
                                // the CLI ignores columns it doesn't use.
                                string pinNum = PR.pin.name;
                                string padNum = "";
                                PR.pin.contacts(C) {
                                    padNum = C.name;
                                    break;
                                }

                                // Component = the device name (falling
                                // back to value, then refdes), not a
                                // duplicate of the RefDes column.
                                string compName = PR.part.device.name;
                                if (compName == "") compName = PR.part.value;
                                if (compName == "") compName = PR.part.name;

                                printf("\"%s\",\"%s\",\"%s\",\"%s\",\"%s\"\n",
                                    csvField(PR.part.name),
                                    csvField(pinNum),
                                    csvField(compName),
                                    csvField(N.name),
                                    csvField(padNum));
                                success = 1;
                            }
                        }
                    }
                }
            }
        }
    }

    return success ? 1 : 0;
}

// ── Main execution ─────────────────────────────────────────────────────────

loadSettings();

// First run (no settings yet): default the output away from the hidden,
// often write-protected AppData ULP folder.
if (!settingsLoaded) {
    outputDir = defaultOutputDir();
}

// This ULP automates generation through PowerShell and cmd.exe, so it is
// Windows-only. EAGLE/Fusion normalizes Windows paths to "C:/...", so a
// missing drive letter in this ULP's own location means macOS/Linux.
if (strlen(ulpDir) < 2 || ulpDir[1] != ':') {
    dlgMessageBox("This ULP automates PinmapGen using Windows tools\n"
        "(PowerShell, cmd.exe) and runs on Windows only.\n\n"
        "On macOS or Linux, use the command line instead - from the\n"
        "PinmapGen repository folder:\n\n"
        "  python3 -m tools.pinmapgen.cli --help\n\n"
        "See docs/usage.md for the full CLI workflow.", "OK");
    exit(0);
}

int result = dlgDialog("PinmapGen - Automated Pinmap Generation") {
    dlgVBoxLayout {
        dlgLabel("Automatic netlist generation from schematic");
        dlgSpacing(5);

        dlgHBoxLayout {
            dlgLabel("PinmapGen repository:");
            dlgStringEdit(repoDir);
            dlgPushButton("Browse...") {
                string picked = dlgDirectory("Select the PinmapGen repository folder", repoDir);
                if (picked != "") {
                    repoDir = cleanPath(picked);
                    dlgRedisplay();
                }
            }
        }
        dlgLabel("(folder containing the cloned PinmapGen repo - saved for next time)");
        dlgSpacing(5);

        dlgHBoxLayout {
            dlgLabel("Project Name:");
            dlgStringEdit(projectName);
            dlgPushButton("Add Timestamp") {
                projectName = generateProjectName(projectName);
                dlgRedisplay();
            }
        }
        dlgSpacing(5);

        dlgHBoxLayout {
            dlgLabel("MCU Type:");
            dlgStringEdit(mcuType);
        }
        // Each quick button calls dlgRedisplay() so the text field above
        // visibly updates - without it, EAGLE dialogs leave the old value
        // on screen and the buttons look broken.
        dlgHBoxLayout {
            dlgPushButton("RP2040")  { mcuType = "rp2040"; dlgRedisplay(); }
            dlgPushButton("RP2350")  { mcuType = "rp2350"; dlgRedisplay(); }
            dlgPushButton("ESP32")   { mcuType = "esp32"; dlgRedisplay(); }
            dlgPushButton("ESP32-S3") { mcuType = "esp32s3"; dlgRedisplay(); }
            dlgPushButton("ESP32-C3") { mcuType = "esp32c3"; dlgRedisplay(); }
        }
        dlgHBoxLayout {
            dlgPushButton("STM32G0")   { mcuType = "stm32g0"; dlgRedisplay(); }
            dlgPushButton("STM32F411") { mcuType = "stm32f411"; dlgRedisplay(); }
            dlgPushButton("STM32H743") { mcuType = "stm32h743"; dlgRedisplay(); }
            dlgPushButton("nRF52840")  { mcuType = "nrf52840"; dlgRedisplay(); }
        }
        dlgHBoxLayout {
            dlgPushButton("ATmega328P") { mcuType = "atmega328p"; dlgRedisplay(); }
            dlgPushButton("ATmega2560") { mcuType = "atmega2560"; dlgRedisplay(); }
            dlgPushButton("SAMD21")     { mcuType = "atsamd21"; dlgRedisplay(); }
            dlgPushButton("SAMD51")     { mcuType = "atsamd51"; dlgRedisplay(); }
        }
        dlgSpacing(5);

        dlgHBoxLayout {
            dlgLabel("MCU Reference:");
            dlgStringEdit(mcuRef);
            dlgPushButton("Analyze") {
                string analysis = analyzeSchematic(mcuRef);
                dlgMessageBox(analysis, "OK");
            }
        }
        dlgSpacing(5);

        dlgHBoxLayout {
            dlgLabel("Base Output Directory:");
            dlgStringEdit(outputDir);
            dlgPushButton("Browse...") {
                string picked = dlgDirectory("Select the output folder", outputDir);
                if (picked != "") {
                    outputDir = cleanPath(picked);
                    dlgRedisplay();
                }
            }
        }
        dlgHBoxLayout {
            dlgPushButton("Default Folder") {
                outputDir = defaultOutputDir();
                dlgRedisplay();
            }
        }
        dlgSpacing(10);

        dlgLabel("Output Formats:");
        dlgSpacing(2);
        dlgHBoxLayout {
            dlgCheckBox("MicroPython", generateMicroPython);
            dlgCheckBox("Arduino", generateArduino);
        }
        dlgHBoxLayout {
            dlgCheckBox("Documentation", generateMarkdown);
            dlgCheckBox("Mermaid Diagrams", generateMermaid);
        }
        dlgSpacing(10);

        dlgPushButton("Preview Generation") {
            string preview = "Generation Preview:\n\n";
            preview += "Project: " + projectName + "\n";
            preview += "MCU: " + mcuType + " (Reference: " + mcuRef + ")\n\n";
            preview += "Output Directory:\n" + outputDir + "/" + projectName + "\n\n";
            preview += "Files that will be generated:\n";
            if (generateMicroPython) preview += "- firmware/micropython/pinmap_micropython.py\n";
            if (generateArduino) preview += "- firmware/include/pinmap_arduino.h\n";
            if (generateMarkdown) preview += "- firmware/docs/PINOUT.md\n";
            if (generateMermaid) preview += "- firmware/docs/pinout.mmd\n";
            preview += "- pinmaps/pinmap.json\n\n";

            string analysis = analyzeSchematic(mcuRef);
            preview += "Schematic Analysis:\n" + analysis;

            dlgMessageBox(preview, "OK");
        }
    }
    dlgHBoxLayout {
        dlgPushButton("-Cancel") dlgReject();
        dlgPushButton("+Generate Pinmap") dlgAccept();
    }
};

if (result) {
    // Normalize what the user typed or pasted before using any of it.
    repoDir = cleanPath(repoDir);
    outputDir = cleanPath(outputDir);
    mcuRef = cleanPath(mcuRef);
    mcuType = cleanPath(mcuType);
    mcuType = strlwr(mcuType);

    // Validate inputs first; settings are saved only once they pass, so
    // rejected values are never persisted for the next run.
    string validationErrors = validateInputs(mcuRef, outputDir, projectName, repoDir);

    // A custom TOML profile dropped into the repository is a legitimate
    // MCU type the built-in list doesn't know - offer to proceed and let
    // the CLI validate it for real.
    if (strlen(validationErrors) == 0 && !isValidMcu(mcuType)) {
        int choice = dlgMessageBox("MCU type '" + mcuType + "' is not one of the built-in profiles:\n" +
            validMcuList + "\n\n" +
            "If it is a custom TOML profile inside the repository's\n" +
            "tools/pinmapgen/profiles/ folder it can still work - the\n" +
            "CLI validates the profile for real.", "Use anyway", "-Cancel");
        if (choice != 0) exit(0);
    }

    string fullOutputDir = outputDir + "/" + projectName;

    if (strlen(validationErrors) == 0) {
        saveSettings();

        // Create project output directory. cmd.exe /c is required because
        // mkdir is a cmd built-in (not an executable) and 2>nul is cmd
        // redirection syntax; backslashes because cmd rejects
        // forward-slash paths.
        system("cmd.exe /c mkdir \"" + toWindowsPath(fullOutputDir) + "\" 2>nul");

        // Find a working Python 3.11+ up front so a missing or too-old
        // interpreter fails fast with a clear message, instead of a dead
        // CLI run with no log.
        string pythonCmd = findPython(fullOutputDir);
        if (pythonCmd == "") {
            dlgMessageBox("Python 3.11 or newer was not found.\n\n"
                "Install it from python.org/downloads and tick the\n"
                "'Add python.exe to PATH' box in the installer, then run\n"
                "this ULP again.\n\n"
                "(Both 'python' on PATH and the 'py -3' launcher were\n"
                "checked.)", "OK");
            exit(0);
        }

        // The Analyze button already knows how to answer "does this
        // reference exist?" - so never run a generation that is doomed
        // to produce an empty pinmap.
        if (!refdesExists(mcuRef)) {
            dlgMessageBox("MCU reference '" + mcuRef + "' was not found in the open schematic.\n\n" +
                "Use the Analyze button next to the MCU Reference field to\n" +
                "inspect the schematic, fix the reference, and generate again.", "OK");
            exit(0);
        }

        // Generate netlist automatically from schematic
        string netlistFile = fullOutputDir + "/auto_netlist.csv";
        int netlistResult = generateNetlistCSV(netlistFile);

        if (netlistResult == 1) {
            // Every run mirrors its console output into this log via the
            // CLI's --log-file option; the dialogs below display it.
            string logFile = fullOutputDir + "/pinmapgen_log.txt";

            // Use PowerShell to run PinmapGen CLI from the configured
            // repo. -NoProfile keeps user profiles from interfering, and
            // the trailing 'exit $LASTEXITCODE' makes powershell.exe
            // report the CLI's exit code instead of its own.
            string pinmapCmd = "powershell -NoProfile -Command \"cd '" + psEscape(repoDir) + "'; " + pythonCmd + " -m tools.pinmapgen.cli --csv '" + psEscape(netlistFile) + "' --mcu " + mcuType + " --mcu-ref " + mcuRef + " --out-root '" + psEscape(fullOutputDir) + "' --log-file '" + psEscape(logFile) + "'";

            // The format checkboxes map to real CLI flags now -
            // unchecking one genuinely skips that file.
            if (generateMermaid) {
                pinmapCmd += " --mermaid";
            }
            if (!generateMicroPython) {
                pinmapCmd += " --no-micropython";
            }
            if (!generateArduino) {
                pinmapCmd += " --no-arduino";
            }
            if (!generateMarkdown) {
                pinmapCmd += " --no-markdown";
            }

            pinmapCmd += " --verbose; exit $LASTEXITCODE\"";

            // Remove any stale log from a previous run so a missing file
            // afterwards reliably means Python never started this time.
            system("cmd.exe /c del \"" + toWindowsPath(logFile) + "\" 2>nul");

            int cliResult = system(pinmapCmd);
            string logContent = readLogFile(logFile);

            if (cliResult == 0 && logContent != "" && !logHasIssues(logContent)) {
                // Clean run: no warnings, no errors, no dropped pins.
                string successMsg = "Pinmap Generation Complete!\n\nProject: " + projectName + "\nMCU: " + mcuType + " (" + mcuRef + ")\n\nGenerated files:\n";
                successMsg += "- pinmaps/pinmap.json\n";
                if (generateMicroPython) successMsg += "- firmware/micropython/pinmap_micropython.py\n";
                if (generateArduino) successMsg += "- firmware/include/pinmap_arduino.h\n";
                if (generateMarkdown) successMsg += "- firmware/docs/PINOUT.md\n";
                if (generateMermaid) successMsg += "- firmware/docs/pinout.mmd\n";
                successMsg += "\nLocation: " + fullOutputDir + "\nRun log: " + logFile;

                // Clean up temp netlist
                system("cmd.exe /c del \"" + toWindowsPath(netlistFile) + "\" 2>nul");

                dlgMessageBox(successMsg, "OK");
                system("explorer \"" + toWindowsPath(fullOutputDir) + "\"");
            } else if (cliResult == 0 && logContent != "") {
                // Files were generated, but the CLI reported warnings,
                // validation errors, or dropped pins - show them instead
                // of pretending the run was clean. The netlist is kept
                // for troubleshooting.
                showRunLog(
                    "Pinmap Generated With Issues",
                    "PinmapGen finished, but reported issues you should review\nbefore trusting the generated files.\n\nOutput: " + fullOutputDir,
                    logContent);
                system("explorer \"" + toWindowsPath(fullOutputDir) + "\"");
            } else if (logContent != "") {
                // The CLI ran and failed - the log has the real reason.
                showRunLog(
                    "Pinmap Generation Failed",
                    "The PinmapGen CLI reported an error. The log below shows\nthe reason. The exported netlist was kept for troubleshooting:\n" + netlistFile,
                    logContent);
                system("explorer \"" + toWindowsPath(fullOutputDir) + "\"");
            } else {
                // No log file was written: Python never started, so the
                // failure happened before the CLI could run.
                string errorMsg = "The PinmapGen CLI did not start (no log file was created).\n\n";
                errorMsg += "Python was detected (" + pythonCmd + "), so the most likely causes are:\n";
                errorMsg += "- The PinmapGen repository path is wrong:\n  " + repoDir + "\n";
                errorMsg += "- The repository copy is older than this ULP\n";
                errorMsg += "  (it must support the --log-file option - update both together)\n";
                errorMsg += "- Security software blocked the PowerShell command\n\n";
                errorMsg += "Expected log location:\n" + logFile;

                dlgMessageBox(errorMsg, "OK");
            }
        } else {
            // Handle specific netlist generation errors. dlgMessageBox's
            // second argument is the button label, so it is always "OK";
            // each message opens with its own headline instead.
            string errorMsg = "";

            if (netlistResult == -1) {
                errorMsg = "No schematic is currently open.\n\nPlease:\n1. Open a schematic in Fusion Electronics\n2. Make sure it contains components\n3. Run this ULP again";
            } else if (netlistResult == -2) {
                errorMsg = "No components found in the schematic.\n\nPlease:\n1. Add components to your schematic\n2. Make sure they have reference designators\n3. Connect them with nets";
            } else if (netlistResult == -3) {
                errorMsg = "No nets found in the schematic.\n\nPlease:\n1. Connect your components with wires/nets\n2. Make sure nets have names\n3. Check that components are properly placed";
            } else {
                errorMsg = "Unknown error during netlist generation.\n\nPlease check that:\n1. Schematic has components with pins\n2. Components are connected with nets\n3. You have write permissions to:\n   " + fullOutputDir;
            }

            dlgMessageBox(errorMsg, "OK");
        }
    } else {
        dlgMessageBox("Please fix the following issues:\n\n" + validationErrors, "OK");
    }
}

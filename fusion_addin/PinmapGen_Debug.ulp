#usage "PinmapGen Debug - Test Basic Functionality"

string outputDir = "C:/Users/ZCohe/Desktop";
string projectName = "Debug";

// Main execution
int result = dlgDialog("PinmapGen Debug Test") {
    dlgVBoxLayout {
        dlgLabel("🔧 Debug Mode - Testing Basic Functions");
        dlgSpacing(10);
        
        dlgPushButton("Test 1: Create Directory") {
            string fullPath = outputDir + "/" + projectName;
            int mkdirResult = system("mkdir \"" + fullPath + "\" 2>nul");
            string resultStr;
            sprintf(resultStr, "%d", mkdirResult);
            string msg = "Directory creation attempted.\nPath: " + fullPath + "\nResult: " + resultStr;
            dlgMessageBox(msg, "Test 1 Result");
        }
        
        dlgPushButton("Test 2: Create Test File") {
            string fullPath = outputDir + "/" + projectName;
            string testFile = fullPath + "/test.txt";
            system("mkdir \"" + fullPath + "\" 2>nul");
            output(testFile) {
                printf("Hello from ULP!\nTimestamp: %u\n", time());
            }
            dlgMessageBox("Test file created at:\n" + testFile, "Test 2 Result");
            system("explorer \"" + fullPath + "\"");
        }
        
        dlgPushButton("Test 3: Check Schematic") {
            if (!schematic) {
                dlgMessageBox("No schematic is open!", "Test 3 Result");
            } else {
                int componentCount = 0;
                int netCount = 0;
                
                schematic(S) {
                    S.sheets(SH) {
                        SH.nets(N) {
                            netCount++;
                            N.segments(SEG) {
                                SEG.pinrefs(PR) {
                                    if (PR.part && PR.pin) {
                                        componentCount++;
                                    }
                                }
                            }
                        }
                    }
                }
                
                string netStr;
                string compStr;
                sprintf(netStr, "%d", netCount);
                sprintf(compStr, "%d", componentCount);
                string msg = "Schematic found!\n\nNets: " + netStr + "\nComponents: " + compStr;
                dlgMessageBox(msg, "Test 3 Result");
            }
        }
        
        dlgPushButton("Test 4: Run CLI") {
            string fullPath = outputDir + "/" + projectName;
            string csvFile = fullPath + "/test_netlist.csv";
            
            // Create simple CSV
            system("mkdir \"" + fullPath + "\" 2>nul");
            output(csvFile) {
                printf("\"RefDes\",\"Pin\",\"Component\",\"Net\"\n");
                printf("\"U1\",\"1\",\"U1\",\"VCC\"\n");
                printf("\"U1\",\"2\",\"U1\",\"GND\"\n");
            }
            
            // Run CLI
            string cmd = "powershell -Command \"cd 'C:\\Users\\ZCohe\\OneDrive\\Documents\\Python Scripts\\Fusion_PinMapGen'; python -m tools.pinmapgen.cli --csv '" + csvFile + "' --mcu rp2040 --mcu-ref U1 --out-root '" + fullPath + "' --verbose\"";
            int cliResult = system(cmd);
            
            string cliResultStr;
            sprintf(cliResultStr, "%d", cliResult);
            string msg = "CLI executed!\nResult: " + cliResultStr + "\nCheck: " + fullPath;
            dlgMessageBox(msg, "Test 4 Result");
            system("explorer \"" + fullPath + "\"");
        }
    }
    dlgHBoxLayout {
        dlgPushButton("-Close") dlgReject();
    }
};
